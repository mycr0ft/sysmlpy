// XPECT noErrors ---> ""
package pkg {
	calc def 'F1';
	calc def 'F2';
	calc def 'F3';
	calc def 'F4';
	    
	part def A {
	 	calc f1 : F1;
    	calc f2: F2;
    	calc f3: F3;
    	calc f4: F4;
   	}
}
